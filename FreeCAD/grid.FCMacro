path = '/Users/bichanwu/Desktop/CAD/' # the path to file: util.py, chamber_base.FCStd, mat file with grid parameters
grid_mat = 'tmp.mat' # mat file with grid parameters

### load chamber base
sys.path.append(path)
FreeCAD.openDocument(path + 'chamber_base.FCStd')
#App.newDocument("chamber_base")

### getting parameters for grids
cylinder_h = 10 # temporarily not reading this

# reading parameters
import scipy.io
data = scipy.io.loadmat(path+grid_mat)

hole_d   = data['params']['hole_d'][0][0][0][0]
hole_r   = data['params']['hole_r'][0][0][0][0]
cylinder_r = data['params']['cylinder_r'][0][0][0][0]
angle    = data['params']['angle'][0][0][0][0]
rotation = data['params']['rotation'][0][0][0][0]
# cylinder_r = 8.75
# hole_r=0.5
# hole_d=1.5
# angle=25
# rotation=0


### sketch holes
from util import cal_grid_center
(x_mm,y_mm) = cal_grid_center(cylinder_r,cylinder_h,hole_r,hole_d,angle,rotation)
App.activeDocument().addObject('Sketcher::SketchObject', 'Sketch_grid')
for x, y in zip(x_mm, y_mm):
	App.activeDocument().getObject('Sketch_grid').addGeometry(Part.Circle(App.Vector(x,y,0),App.Vector(0,0,1),hole_r),False)


### extrude grid to 3D
import math
App.activeDocument().addObject('Part::Extrusion','Extrude')
f = App.activeDocument().getObject('Extrude')
f.Base = App.activeDocument().getObject('Sketch_grid')
f.DirMode = "Custom"
f.Dir = App.Vector(-math.tan(angle*math.pi/180)*math.cos(rotation*math.pi/180)*10, -math.tan(angle*math.pi/180)*math.sin(rotation*math.pi/180)*10, 10)
f.LengthRev = cylinder_h / math.cos(angle*math.pi/180)
f.Solid = True
App.activeDocument().getObject('Sketch_grid').Visibility = False
FreeCAD.activeDocument().getObject('Extrude').Placement = App.Placement(App.Vector(0,0,5+cylinder_h),App.Rotation(App.Vector(0,0,1),0))



### cut out grid holes
App.activeDocument().addObject("Part::Cut","Cut")
App.activeDocument().Cut.Base = App.activeDocument().Body
App.activeDocument().Cut.Tool = App.activeDocument().Extrude
Gui.activeDocument().Body.Visibility=False
Gui.activeDocument().Extrude.Visibility=False
App.getDocument('chamber_base').getObject('Cut').ViewObject.ShapeColor=getattr(App.getDocument('chamber_base').getObject('Body').getLinkedObject(True).ViewObject,'ShapeColor',App.getDocument('chamber_base').getObject('Cut').ViewObject.ShapeColor)
App.getDocument('chamber_base').getObject('Cut').ViewObject.DisplayMode=getattr(App.getDocument('chamber_base').getObject('Body').getLinkedObject(True).ViewObject,'DisplayMode',App.getDocument('chamber_base').getObject('Cut').ViewObject.DisplayMode)
App.ActiveDocument.recompute()

### save object

import Mesh
__objs__=[]
__objs__.append(FreeCAD.getDocument("chamber_base").getObject("Cut"))
Mesh.export(__objs__,path+"Grid_to_print.stl")
del __objs__
#App.closeDocument('chamber_base')
